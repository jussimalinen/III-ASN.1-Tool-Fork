CIDMODULE DEFINITIONS  AUTOMATIC TAGS  ::=
BEGIN
IMPORTS NonStandardParameter, CallIdentifier FROM H323-MESSAGES;
CID ::= CallIdentifier
END

ADDRESS DEFINITIONS  AUTOMATIC TAGS  ::=
BEGIN
IMPORTS		TransportAddress FROM  H323-MESSAGES -- see H.225
			TransportAddress FROM  MULTIMEDIA-SYSTEM-CONTROL; -- see H.245
Address ::= INTEGER
END

ALTERNATEGK-MODULE DEFINITIONS AUTOMATIC TAGS ::=
BEGIN
IMPORTS AlternateGK FROM H323-MESSAGES;
Address ::= INTEGER
END
